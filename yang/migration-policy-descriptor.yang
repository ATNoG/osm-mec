module migration-policy-descriptor {
  namespace "http://example.com/ns/migration-policy-descriptor";
  prefix mp;

  description "YANG module for Migration Policy Descriptor.";
  
  typedef relational-operation-type {
    description
      "The relational operator used to define whether a migration
        should be triggered in certain scenarios, such as
        if the metric statistic goes above or below a specified
        value.";
    type enumeration {
        enum GE; // greater than or equal
        enum LE; // less than or equal
        enum GT; // greater than
        enum LT; // less than
        enum EQ; // equal
        enum NE; // not equal
    }
  }

  grouping migration-policy-descriptor {
    description "Migration Policy descriptor attributes.";

    leaf artifact {
      type string;
      description "Name of the artifact that the migration policy is associated with. If it is not specified, the migration policy applies to all artifacts.";
    }

    leaf enabled {
      description "Specifies if the migration policy can be applied.";
      type boolean;
      default true;
    }

    container cpu-criteria {
      description "Criteria that defines when an application migration is executed due to unmet CPU requirements.";

      leaf allocated-cpu {
        description "The amount of CPU resources (in vCPUs) allocated for the application.";
        type uint32;
      }

      leaf cpu-surge-capacity {
        description "The additional CPU resources (in vCPUs) that the host must be able to provide when the application experiences a surge in demand.";
        type uint32;
      }
      
      leaf cpu-threshold-time {
        description "The duration (in seconds) for which the condition can be unmet before application migration is executed.";
        type uint32;
      }

      leaf cooldown-time {
        description "The time (in seconds) that must elapse before the migration policy can be re-evaluated after a migration.";
        type uint32;
      }
    }

    container mem-criteria {
      description "Criteria that defines when an application migration is executed due to unmet memory requirements.";

      leaf allocated-mem {
        description "The amount of memory resources (in MB) allocated for the application.";
        type uint32;
      }

      leaf mem-surge-capacity {
        description "The additional memory resources (in MB) that the host must be able to provide when the application experiences a surge in demand.";
        type uint32;
      }
      
      leaf mem-threshold-time {
        description "The duration (in seconds) for which the condition can be unmet before application migration is executed.";
        type uint32;
      }

      leaf cooldown-time {
        description "The time (in seconds) that must elapse before the migration policy can be re-evaluated after a migration.";
        type uint32;
      }
    }

    container mobility-criteria {
      description "Criteria that defines when an application migration is executed due to unmet mobility requirements.";

      leaf mobility-migration-factor {
        description "Factor ranging from 0 to 1 that influences migration likelihood. A value of 0 prevents migration, while a value of 1 makes migration most likely.";
         type decimal64 {
          fraction-digits 2;
          range "0.0 .. 1.0";
        }
      }
      
      leaf mobility-threshold-time {
        description "The duration (in seconds) for which the condition can be unmet before application migration is executed.";
        type uint32;
      }

      leaf cooldown-time {
        description "The time (in seconds) that must elapse before the migration policy can be re-evaluated after a migration.";
        type uint32;
      }
    }
  }
}
