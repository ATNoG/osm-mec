module mec-app-descriptor {
  namespace "http://example.com/ns/mec-app-descriptor";
  prefix mad;

  import artifact-descriptor { prefix ad; }
  import change-app-instance-state-op-config-descriptor { prefix caisoc; }
  import dns-rule-descriptor { prefix dr; }
  import external-cpd-descriptor { prefix ecpd; }
  import feature-dependency-descriptor { prefix fd; }
  import latency-descriptor { prefix l; }
  import network-policy-descriptor { prefix np; }
  import migration-policy-descriptor { prefix mp; }
  import service-dependency-descriptor { prefix srv; }
  import service-descriptor { prefix sd; }
  import sw-image-descriptor { prefix si; }
  import terminate-app-instance-op-config-descriptor { prefix taio; }
  import traffic-rule-descriptor { prefix trd; }
  import transport-dependency-descriptor {prefix td; }
  import user-context-transfer-capability-descriptor { prefix uctc; }
  import virtual-compute-descriptor { prefix vc; }
  import virtual-storage-descriptor { prefix vs; }

  description "YANG module for MEC Application Descriptors based on ETSI GS MEC 010-2 V2.2.1.";

  container mec-appd {
    leaf id {
      type string;
      mandatory true;
      description "Identifier of this MEC application descriptor. This attribute shall be globally unique.";
    }
    leaf name {
      type string;
      mandatory true;
      description "Name to identify the MEC application.";
    }
    leaf provider {
      type string;
      mandatory true;
      description "Provider of the application and of the AppD.";
    }
    leaf soft-version {
      type string;
      mandatory true;
      description "Identifies the version of software of the MEC application.";
    }
    leaf version {
      type string;
      mandatory true;
      description "Identifies the version of the application descriptor.";
    }
    leaf mec-version {
      type string;
      mandatory true;
      description "Identifies version(s) of MEC system compatible with the MEC application described in this version of the AppD. The value shall be formatted as comma-separated list of strings.";
    }
    leaf info-name {
      type string;
      description "Human readable name for the MEC application.";
    }
    leaf description {
      type string;
      mandatory true;
      description "Human readable description of the MEC application.";
    }
    container virtual-compute {
      uses vc:virtual-compute-descriptor;
      description "Describes CPU and memory requirements, as well as optional additional requirements, such as disk and acceleration related capabilities, of the virtualisation container used to realize this MEC application.";
    }
    container sw-image {
      uses si:sw-image-descriptor;
      description "Describes the descriptors of the software image to be used by the virtualisation container used to realize this MEC application.";
    }
    list virtual-storage {
      key "id";
      uses vs:virtual-storage-descriptor;
      description "Defines descriptors of virtual storage resources to be used by the MEC application.";
    }
    list ext-cpd{
      key "id";
      uses ecpd:external-cpd-descriptor;
      description "Describes external interface(s) exposed by this MEC application.";
    }
    list service-required {
      key "name";
      uses srv:service-dependency-descriptor;
      description "Describes services a MEC application requires to run";
    }
    list service-optional {
      key "name";
      uses srv:service-dependency-descriptor;
      description "Describes services a MEC application may use if available. ";
    }
    list service-produced {
      key "name";
      uses sd:service-descriptor;
      description "Describes services a MEC application is able to produce to the platform or other MEC applications. Only relevant for serviceproducing apps. ";
    }
    container feature-required {
      uses fd:feature-dependency-descriptor;
      description "Describes features a MEC application requires to run";
    }
    container feature-optional {
      uses fd:feature-dependency-descriptor;
      description "Describes features a MEC application may use if available.";
    }
    list transport-dependencies {
      key "id";
      min-elements 1;
      uses td:transport-dependency-descriptor;
      description "Transports, if any, that this application requires to be provided by the platform. These transports will be used by the application to deliver services provided by this application. Only relevant for service-producing apps. See note 2. ";
    }
    list traffic-rule {
      key "id";
      uses trd:traffic-rule-descriptor;
      description "Describes traffic rules the MEC application requires.";
    }
    list dns-rule {
      key "id";
      uses dr:dns-rule-descriptor;
      description "Describes DNS rules the MEC application requires.";
    }
    container latency {
      uses l:latency-descriptor;
      description "Describes the maximum latency tolerated by the MEC application. ";
    }
    container terminate-app-instance-op-config {
      uses taio:terminate-app-instance-op-config-descriptor;
      description "Configuration parameters for the Terminate application instance operation. ";
    }
    container change-app-instance-state-op-config {
      uses caisoc:change-app-instance-state-op-config-descriptor;
      description "Configuration parameters for the change application instance state operation. ";
    }
    container user-context-transfer-capability {
      uses uctc:user-context-transfer-capability-descriptor;
      description "If the application supports the user context transfer capability, this attribute shall be included.";
    }
    container network-policy {
      uses np:network-policy-descriptor;
      description "If present, it represents the application network policy of carrying the application traffic.";
    }

    list migration-policy {
      key "artifact";
      config false;
      uses mp:migration-policy-descriptor;
      description "If present, it represents the application monitoring policy";
    }

    list artifacts {
      description "List of artifacts required by the MEC application.";
      key "name";
      uses ad:artifact-descriptor;
    }
  }
}
